FME workspace test.fmw

Parameters:
- SourceDataset_KINETICA = asdf   # Source Kinetica Database(s)
- DestDataset_CSV2 = $(FME_HOME)pluginbuilder\gpudb-connector-fme\Examples   # Destination CSV (Comma Separated Value) Folder
- SourceDataset_KINETICA_3 = no charN   # Source Kinetica Database(s)
- DestDataset_CSV2_3 = $(FME_HOME)pluginbuilder\gpudb-connector-fme\Examples   # Destination CSV (Comma Separated Value) Folder
- DestDataset_KINETICA = test_wkt_geom   # Destination Kinetica Folder

Readers:
- KINETICA_1: KINETICA from $(SourceDataset_KINETICA)
- KINETICA_2: KINETICA from $(SourceDataset_KINETICA_3)

Writers:
- CSV2_1: CSV2 to $(DestDataset_CSV2)
- CSV2_2: CSV2 to $(DestDataset_CSV2_3)
- KINETICA_3: KINETICA to $(DestDataset_KINETICA)

KineticaFeatureType (reader KINETICA_1)
    attributes: wkt string
    -> geom_kin (writer KINETICA_3)
geom_kin (writer KINETICA_3)
    attributes: wkt WKT
KineticaFeatureType (reader KINETICA_2)
    attributes: i1 int32, i2 int32, i8 int32, i16 int32, d1 real64, f1 real32, l1 int64, timestamp int64, s1 string, date string, datetime string, decimal string, ipv4 string, time string, c1 string, c2 string, c4 string, c8 string, c16 string, c32 string, c64 string, c128 string, c256 string, wkt string
    -> test_data_all_but_charN (writer CSV2_2)
test_data_all_but_charN (writer CSV2_2)
    attributes: i1 int32, i2 int32, i8 int32, i16 int32, d1 real64, f1 real32, l1 int64, timestamp int64, s1 string, date string, datetime string, decimal string, ipv4 string, time string, c1 string, c2 string, c4 string, c8 string, c16 string, c32 string, c64 string, c128 string, c256 string, wkt string
KineticaFeatureType (writer CSV2_1)
    attributes: wkt string
test_wkty_only_kinetica (writer KINETICA_3)
    attributes: wkt WKT
