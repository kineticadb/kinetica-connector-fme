FME workspace KineticaToCSV_all_but_charN.fmw

Parameters:
- SourceDataset_KINETICA = test_table_all_but_charN   # Source Kinetica Database(s)
- DestDataset_CSV2 = $(FME_HOME)pluginbuilder\gpudb-connector-fme\Examples   # Destination CSV (Comma Separated Value) Folder

Readers:
- KINETICA_1: KINETICA from $(SourceDataset_KINETICA)

Writers:
- CSV2_1: CSV2 to $(DestDataset_CSV2)

KineticaFeatureType (reader KINETICA_1)
    attributes: i1 int32, i2 int32, i8 int32, i16 int32, d1 real64, f1 real32, l1 int64, timestamp int64, s1 string, date string, datetime string, decimal string, ipv4 string, time string, wkt string
    -> all_data_types_but_charN (writer CSV2_1)
all_data_types_but_charN (writer CSV2_1)
    attributes: i1 int32, i2 int32, i8 int32, i16 int32, d1 real64, f1 real32, l1 int64, timestamp int64, s1 string, date string, datetime string, decimal string, ipv4 string, time string, wkt string
