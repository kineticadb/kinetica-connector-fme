FME workspace csvToKinetica.fmw

Parameters:
- SourceDataset_CSV2 = $(FME_HOME)pluginbuilder\gpudb-connector-fme\Examples\track_data.csv   # Source CSV (Comma Separated Value) File(s)
- DestDataset_KINETICA = test_fme_table   # Destination Kinetica Folder

Readers:
- CSV2_1: CSV2 from $(SourceDataset_CSV2)

Writers:
- KINETICA_1: KINETICA to $(DestDataset_KINETICA)

CSV (reader CSV2_1)
    attributes: x string, y string, TRACKID string, TIMESTAMP string
    -> fme_test_table (writer KINETICA_1)
fme_test_table (writer KINETICA_1)
    attributes: x real64, y real64, TRACKID string, TIMESTAMP real64
