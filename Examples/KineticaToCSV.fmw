FME workspace KineticaToCSV.fmw

Parameters:
- SourceDataset_KINETICA = test_fme_table   # Source Kinetica Database(s)
- DestDataset_CSV2 = $(FME_HOME)pluginbuilder\gpudb-connector-fme\Examples   # Destination CSV (Comma Separated Value) Folder

Readers:
- KINETICA_1: KINETICA from $(SourceDataset_KINETICA)

Writers:
- CSV2_1: CSV2 to $(DestDataset_CSV2)

KineticaFeatureType (reader KINETICA_1)
    attributes: x real64, y real64, TRACKID string, TIMESTAMP real64
    -> track_data_out (writer CSV2_1)
track_data_out (writer CSV2_1)
    attributes: x real64, y real64, TRACKID string, TIMESTAMP real64
